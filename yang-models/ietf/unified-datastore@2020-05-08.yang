module unified-datastore {
    yang-version 1.1;
    namespace "fkie";
    prefix "ud";

    organization
        "Fraunhofer FKIE";

    contact
        "Author: Henning Rogge <mailto:henning.rogge@fkie.fraunhofer.de>";

    description
        "Definition of the Restconf unified datastore as a real module";

    revision 2020-05-08 {
        description "Initial revision.";
    }

    import ietf-restconf {
        prefix "ietf-restconf";
    }

    uses ietf-restconf:restconf;
}
